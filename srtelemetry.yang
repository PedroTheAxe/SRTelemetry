module srtelemetry {

    yang-version "1";

    // namespace
    namespace "urn:srl_nokia_ext/srtelemetry";
    prefix "srtelemetry";

    import srl_nokia-common {
        prefix srl-comm;
    }

    import srl_nokia-system {
        prefix srl-system;
    }
    
    import srl_nokia-network-instance {
        prefix srl-netinst;
    }

    import srl_nokia-extensions {
        prefix srl-ext;
    }

    // description
    description  "SRTelemetry YANG module";

    // revision(s)
    revision "2023-05-12" {
        description "SRTelemetry YANG module 1.0";
    }

    grouping srtelemetry-top {
        description "Top level grouping for srtelemetry sample app";

        container srtelemetry {
            presence "presence container";
            description "Top level enclosing container for srtelemetry sample app config and operational state data";

            leaf address {
                type srl-comm:ip-address;
                default "::";
                srl-ext:show-importance high;
                description "IP Address the prometheus exporter server listens on";
            }
            leaf port {
                type srl-comm:port-number;
                default "8888";
                srl-ext:show-importance high;
                description "Port number the prometheus exporter server listens on";
            }
            leaf network-instance {
                type leafref {
                    path "/srl-netinst:network-instance/srl-netinst:name";
                }
                srl-ext:show-importance high;
                default "mgmt";
                description "Reference to a configured network-instance used to send out telemetry updates This network-instance must already exist in the system.";

            } // container srtelemetry
        } // grouping srtelemetry-top

    }

    augment "/srl-system:system" {
        uses srtelemetry-top;
    }

}
